import FreeCAD
import PartDesign
import PartDesignGui
import Sketcher
from PySide.QtGui import QWidget, QLabel, QLineEdit, QComboBox, QVBoxLayout, QFormLayout, QPushButton, QCheckBox, QGroupBox
import numpy as np
from math import pi, sqrt, sin, cos, acos, atan



"""
	Overview:
	-----------------------------------------------------------------------------------------------
   	Nosecone is a macro written to automagically(tm) create a parametric nosecone within a 
	PartDesign body. The following aerodynamic profiles may be generated:
	
	- Conic
	- Biconic
	- Tangent Ogive
	- Secant Ogive
	- HAACK
	- Power Series
	- Elliptical
	- Parabolic
	
	Additionally, conic, biconic, and tangent ogive nosecones may be 'spherically blunted', with a 
	tangent spherical cap replacing the sharp tip. More blunted nosecone geometries are being added
	as well.
	
   	Description of Nosecone Geometry:
	-----------------------------------------------------------------------------------------------
	The nosecone consists of the 'profile' section, and the 'shoulder' section. The profile is the 
	pointy bit, with a specified profile curve.
	
	This curve has a given length and base diameter. The length is defined by the 'fineness ratio', 
	which is the ratio between the length and base diameter, L / D.
	
	The shoulder section is used to locate the nosecone within a rocket's body tube. It is a 
	cylindrical boss behind the profile section.
	
	If specified, the nosecone will be made hollow, with a constant wall thickness, making a much 
	lighter component, with room for stowed components.
	
	Current Limitations:
	-----------------------------------------------------------------------------------------------
   	- Please note: at this time, the power series nosecone is unable to solve for thickness at low 
	  values of n.
	- only conic, biconic, and tangent ogive are able to have spherically blunted tips as of now
	
	Planned Features:
	-----------------------------------------------------------------------------------------------
	- Addition of a NoseCone object that allow recomputation by altering data fields.
	- Accepting VarSet variables as inputs
	- Spherical blunting for all nosecone types

	Other:
	-----------------------------------------------------------------------------------------------
   	For Mathematical Descriptions of profiles: https://en.wikipedia.org/wiki/Nose_cone_design
"""



__Name__ = 'Nosecone'
__Comment__ = 'Draws a parametric nosecone for a rocket.'
__Author__ = 'Michael Stoll'
__Version__ = '0.3'
__Date__ = '2026-04-09'
__License__ = 'GPL-3.0'
__Web__ = 'https://github.com/DeltaFwulf/rocket-macro-fc'
__Wiki__ = 'N/A'
__Icon__ = 'MyMacro.svg, please put an svg file along side the macro, respecting the macro filename'
__Help__ = 'To build a nosecone, open a standard file, run the macro, and select desired geometry by filling out the fields, then clicking the make nosecone button.'
__Status__ = 'Alpha'
__Requires__ = 'FreeCAD >1.0'
__Communication__ = 'https://github.com/DeltaFwulf/rocket-macro-fc/issues'
__Files__ = ''



# TODO: have nosecone point to +x by default (currently -x)
# TODO: create a new document if one isn't already open
# TODO: if nosecone fails to generate, delete it?



class InputWindow(QWidget):

	def __init__(self):	
		
		super(InputWindow, self).__init__()
		self.profiles = {'conic':self.conic, 
						'biconic':self.biconic, 
						'haack':self.haack, 
						'elliptical':self.elliptical, 
						'power-series':self.powerSeries,
						'parabolic':self.parabolic,
						'tangent-ogive':self.tangentOgive,
						'secant-ogive': self.secantOgive}
		
		self._inShape = QComboBox()
		self._inShape.addItems([key for key in self.profiles.keys()])
		self._inShape.currentTextChanged.connect(self.addFurtherInputFields) # this runs when a new nosecone is picked
		self._inBaseDiameter = QLineEdit()
		self._inFinenessRatio = QLineEdit()
		self._inShoulderDiameter = QLineEdit()
		self._inShoulderLength = QLineEdit()
		self._inWallThickness = QLineEdit()
		self._inCapShoulder = QCheckBox()
		self._inForward = QComboBox()
		self._inForward.addItems(['+x', '-x', '+y', '-y', '+z', '-z'])
		
		self._makeNosecone = QPushButton("Make Nosecone")
		self._makeNosecone.clicked.connect(self.makeNosecone)
		
		self.mainLayout = QVBoxLayout()
	
		# shared inputs are in this layout section
		self.baseInputs = QGroupBox("Common Inputs")
		comLayout = QFormLayout()
		comLayout.addRow('Shape', self._inShape)
		comLayout.addRow('Base Diameter', self._inBaseDiameter)
		comLayout.addRow('Fineness Ratio', self._inFinenessRatio)
		comLayout.addRow('Shoulder Diameter', self._inShoulderDiameter)
		comLayout.addRow('Shoulder Length', self._inShoulderLength)
		comLayout.addRow('Wall Thickness', self._inWallThickness)
		comLayout.addRow('Capped Shoulder', self._inCapShoulder)
		comLayout.addRow('Forward Direction', self._inForward)
		self.baseInputs.setLayout(comLayout)
		
		self.furtherInputs = QGroupBox("Further Inputs")
		self.mainLayout.addWidget(self.baseInputs)
		self.mainLayout.addWidget(self.furtherInputs)
		self.mainLayout.addWidget(self._makeNosecone)
		self.addFurtherInputFields()
		self.setLayout(self.mainLayout)
		self.show()
		
		
	def addFurtherInputFields(self):
		"""When a nosecone geometry is selected, this function runs, and adds required input fields if necessary."""
		
		self.mainLayout.itemAt(1).widget().deleteLater()
		furtherInputs = QGroupBox("Additional Inputs")
		layout = QFormLayout()
		shape = self._inShape.currentText()
		
		match shape:
			case 'biconic':
				self._inSplitNorm = QLineEdit()
				self._inMidDiameter = QLineEdit()
				layout.addRow("Normalised split location (0 = tip, 1 = base)", self._inSplitNorm)
				layout.addRow("Mid diameter", self._inMidDiameter)
	
			case 'haack':
				self._inC = QLineEdit()							
				layout.addRow("C (0 to 1)" , self._inC)
				
			case 'power-series':
				self._inN = QLineEdit()				
				layout.addRow("n (0 to 1)", self._inN)
				
			case 'parabolic':
				self._inK = QLineEdit()
				layout.addRow("K' (0 to 1)", self._inK)
				
			case 'secant-ogive':
				self._inRho = QLineEdit()
				layout.addRow("Ogive Radius", self._inRho)
		
		if shape in ['conic', 'biconic', 'tangent-ogive']:
			self._inBlunt = QCheckBox()
			self._inBluntRadius = QLineEdit()
			self._inBluntRadius.setText('0.0')
			layout.addRow("Blunted Tip", self._inBlunt)
			layout.addRow("Tip Radius", self._inBluntRadius)
				
		furtherInputs.setLayout(layout)
		self.mainLayout.insertWidget(1, furtherInputs)

		
	def makeNosecone(self):
		
		# Check common inputs	
		try:
			self.shape = self._inShape.currentText()
			self.dBase = float(self._inBaseDiameter.text())
			fRatio = float(self._inFinenessRatio.text())
			self.lCone = fRatio*self.dBase
			self.dShoulder = float(self._inShoulderDiameter.text())
			self.lShoulder = float(self._inShoulderLength.text())
			self.tWall = float(self._inWallThickness.text())
			self.capped = self._inCapShoulder.isChecked()
			fwd = self._inForward.currentText()
			
		except:
			print("One or more common inputs are missing, please check and try again.")
			return
			
		try:
			blunted = self._inBlunt.isChecked()
		except:
			blunted = False
			
		# Step 1: create a body named 'nosecone'
		body = App.activeDocument().addObject('PartDesign::Body', 'nosecone')
		body.Label = ('blunted ' if blunted else '') + self.shape + ' nosecone'
		body.AllowCompound = False
		App.ActiveDocument.recompute()
				
		for feat in body.Origin.OriginFeatures:
			if 'X_Axis' in feat.Name:
				x_axis = feat
			if 'XZ_Plane' in feat.Name:
				sketchPlane = feat
		
		profileSketch = body.newObject('Sketcher::SketchObject','Sketch')
		profileSketch.AttachmentSupport = sketchPlane
		profileSketch.MapMode = 'FlatFace'
		App.ActiveDocument.recompute()

		# Step 3: draw the nosecone sketch	
		out = self.profiles.get(self.shape)(sketch=profileSketch) # draw the nosecone profile
		
		if out != 0:
			print(f"Invalid inputs given for {self.shape}, check and try again.")
			return
			
		for i in range(len(profileSketch.Geometry)):
			profileSketch.addConstraint(Sketcher.Constraint('Block', i))
			
		App.ActiveDocument.recompute()
				
		# Step 4: revolve this sketch about the origin z axis 360 degrees
		revolution = body.newObject('PartDesign::Revolution','Revolution')
		revolution.Profile = profileSketch
		revolution.ReferenceAxis = (App.ActiveDocument.getObject(x_axis.Name), [''])
		revolution.Angle = 360.0
		revolution.Reversed = 0
		profileSketch.Visibility = False
		App.ActiveDocument.recompute()
		
		# Step 5: hollow out the nosecone against the cap face (leave on if selected 'capped'
		thickness = body.newObject('PartDesign::Thickness', 'Thickness')
		thickness.Value = self.tWall
		thickness.Reversed = 1
		thickness.Mode = 0
		thickness.Intersection = 0
		thickness.Join = 1
		
		# Step 5a: identify the rear shoulder face
		for i in range(len(body.Shape.Faces)):
			f = body.Shape.Faces[i]
						
			if abs(f.CenterOfMass[0] - (self.lCone + self.lShoulder)) < 0.001 and abs(f.Area - (pi*self.dShoulder**2 / 4)) < 0.001:
				thickness.Base = (App.ActiveDocument.ActiveObject.BaseFeature, ["Face" + str(i + 1),])
				
		App.ActiveDocument.recompute()
		
		# Step 6: apply end cap if selected
		
		# create the circular sketch
		
		# pad out wall thickness cap
		
		# Step 7: rotate the nosecone to the desired orientation				
		match fwd:
			case '+x':
				rot = FreeCAD.Rotation(App.Vector(0, 1, 0), 180)
			case '-x':
				rot = FreeCAD.Rotation(App.Vector(0, 1, 0), 0)
			case '+y':
				rot = FreeCAD.Rotation(App.Vector(0, 0, 1), -90)
			case '-y':
				rot = FreeCAD.Rotation(App.Vector(0, 0, 1), 90)
			case '+z':
				rot = FreeCAD.Rotation(App.Vector(0, 1, 0), -90)
			case '-z':
				rot = FreeCAD.Rotation(App.Vector(0, 1, 0), 90)
		
		centre = App.Vector(0.0, 0.0, 0.0)
		pos = body.Placement.Base
		newPos = App.Placement(pos, rot, centre)
		body.Placement = newPos
		
		App.ActiveDocument.recompute()
		
		print("Nosecone has been created")
		
				
						
	def conic(self, sketch:Sketcher.Sketch, **kwargs) -> int:
		
		try:
			blunted = self._inBlunt.isChecked()
			rTip = float(self._inBluntRadius.text())
		except:
			return 1
			
		xTip = 0.0
		
		if blunted:
			
			phi = atan(self.dBase / (2*self.lCone))
			rBase = self.dBase / 2
			xt = (2*rTip*self.lCone**2 / self.dBase)*sqrt(1 / (rBase**2 + self.lCone**2))
			yt = xt*rBase / self.lCone
						
			centre = App.Vector(xt + sqrt(rTip**2 - yt**2), 0.0, 0.0)
			xTip = centre[0] - rTip
			dir = App.Vector(0.0, 0.0, 1.0)

			sketch.addGeometry(Part.ArcOfCircle(Part.Circle(centre, dir, rTip), pi/ 2 + phi, pi), False)
			sketch.addGeometry(Part.LineSegment(App.Vector(xt, yt), App.Vector(self.lCone, self.dBase / 2)), False)
			
		else:
			sketch.addGeometry(Part.LineSegment(App.Vector(0.0, 0.0), App.Vector(self.lCone, 0.5*self.dBase)), False)

		sketch.addGeometry(self.plotInnerCurve(xTip=xTip), False)
		
		return 0
		
		
		
	def biconic(self, sketch:Sketcher.Sketch, **kwargs) -> int:
		"""Draws the biconic specific profile."""
		
		xTip = 0.0
		
		try:
			rMid = float(self._inMidDiameter.text()) / 2
			blunted = self._inBlunt.isChecked()
			rTip = float(self._inBluntRadius.text())
			xMid = float(self._inSplitNorm.text())*self.lCone
		except:
			return 1
					
		pMid = App.Vector(xMid, rMid)
		pBase = App.Vector(self.lCone, self.dBase / 2)
		
		if blunted:
			
			phi = atan(rMid / xMid)
			xt = (rTip*xMid**2 / rMid)*sqrt(1 / (rMid**2 + xMid**2))
			yt = xt*rMid / xMid
						
			centre = App.Vector(xt + sqrt(rTip**2 - yt**2), 0.0, 0.0)
			xTip = centre[0] - rTip
			dir = App.Vector(0.0, 0.0, 1.0)
			
			sketch.addGeometry(Part.ArcOfCircle(Part.Circle(centre, dir, rTip), pi / 2 + phi, pi), False)
			sketch.addGeometry(Part.LineSegment(App.Vector(xt, yt), pMid), False)
									
		else:
			sketch.addGeometry(Part.LineSegment(App.Vector(0.0, 0.0), pMid), False)
		
		sketch.addGeometry(Part.LineSegment(pMid, pBase), False)
		
		sketch.addGeometry(self.plotInnerCurve(xTip=xTip), False)
		
		
		return 0
		
	
		
	def tangentOgive(self, sketch:Sketcher.Sketch, **kwargs) -> int:
		
		try:
			blunted = self._inBlunt.isChecked()
			rTip = float(self._inBluntRadius.text())
		except:
			return 1
			
		nPts = 50 if kwargs.get('nPoints') is None else kwargs.get('nPoints')
		R = self.dBase / 2
		xTip = 0.0
		xt = 0.0
		
		if blunted:
			x0 = self.lCone - sqrt((R - rTip)*(self.lCone**2 / R - rTip))
			k = (self.lCone**2 - R**2) / (self.lCone**2 + R**2 - 2*R*rTip)
			yt = rTip*k
			xt = x0 - rTip*sqrt(1 - k**2)	
			xTip = x0 - rTip
			centre = App.Vector(x0, 0.0, 0.0)
			dir = App.Vector(0.0, 0.0, 1.0)
			
			sketch.addGeometry(Part.ArcOfCircle(Part.Circle(centre, dir, rTip), pi / 2 + acos(yt / rTip), pi), False)
						
		rho = (R + self.lCone**2 / R) / 2
		pts = np.zeros((nPts, 2), float)
		pts[:, 0] = np.linspace(xt, self.lCone, nPts, endpoint=True)
		pts[:, 1] = np.sqrt(rho**2 + pts[:, 0]*(2*self.lCone - pts[:, 0]) - self.lCone**2) + R - rho
		sketch.addGeometry(self.makeBSpline(pts), False)
		sketch.addGeometry(self.plotInnerCurve(xTip=xTip), False)
		
		return 0
		
		
		
	def secantOgive(self, sketch:Sketcher.Sketch, **kwargs) -> int:
		"""Similar to the tangent ogive, but with rho != tangent value."""
		
		try:
			rho = float(self._inRho.text())
		except:
			return 1
		
		nPts = 50 if kwargs.get('nPoints') is None else kwargs.get('nPoints')
		R = self.dBase / 2
		alpha = atan(R / self.lCone) - acos(sqrt(R**2 + self.lCone**2) / (2*rho))
		xTip = 0.0
		xt = 0.0
			
		pts = np.zeros((nPts, 2), float)
		pts[:, 0] = np.linspace(xt, self.lCone, nPts, endpoint=True)
		pts[:, 1] = np.sqrt(rho**2 - (pts[:, 0] - rho*cos(alpha))**2) + rho*sin(alpha)
		sketch.addGeometry(self.makeBSpline(pts), False)
		sketch.addGeometry(self.plotInnerCurve(xTip=xTip), False)
		
		return 0
		
		
				
	def haack(self, sketch:Sketcher.Sketch, **kwargs) -> int:
		"""Creates the solid HAACK nosecone sketch"""
		try:
			C = float(self._inC.text())
		except:
			return 1
			
		nPts = 50 if kwargs.get('nPoints') is None else kwargs.get('nPoints')
		theta = np.acos(1 - 2*np.linspace(0, 1, nPts, endpoint=True))
		pts = np.zeros((nPts, 2), float)
		pts[:, 0] = 0.5*self.lCone*(1 - np.cos(theta))
		pts[:, 1] = 0.5*self.dBase / sqrt(pi) * np.sqrt(theta - 0.5*np.sin(2*theta) + C*np.sin(theta)**3)
		sketch.addGeometry(self.makeBSpline(pts), False)
		sketch.addGeometry(self.plotInnerCurve(), False)
		
		return 0	
		
	
	
	def elliptical(self, sketch:Sketcher.Sketch, **kwargs) -> int:
		"""Draws the elliptical nosecone curve."""
		
		nPts = 50 if kwargs.get('nPoints') is None else kwargs.get('nPoints')
		pts = np.zeros((nPts, 2), float)
		pts[:, 0] = np.linspace(0, self.lCone, nPts, endpoint=True)
		pts[:, 1] = (self.dBase / (2*self.lCone))*np.sqrt(pts[:, 0]*(2*self.lCone - pts[:, 0]))
		sketch.addGeometry(self.makeBSpline(pts), False)
		sketch.addGeometry(self.plotInnerCurve(), False)
		
		return 0
		
		
	
	def powerSeries(self, sketch:Sketcher.Sketch, **kwargs) -> int:
		
		try:
			n = float(self._inN.text())
		except:
			return 1
			
		nPts = 50 if kwargs.get('nPoints') is None else kwargs.get('nPoints')
		pts = np.zeros((nPts, 2), float)
		pts[:, 0] = np.linspace(0, self.lCone, nPts, endpoint=True)
		pts[:, 1] = 0.5*self.dBase*(pts[:, 0] / self.lCone)**n
		sketch.addGeometry(self.makeBSpline(pts), False)
		sketch.addGeometry(self.plotInnerCurve(), False)
		
		return 0
		
		
		
	def parabolic(self, sketch:Sketcher.Sketch, **kwargs) -> int:
		
		try:
			k = float(self._inK.text())
		except:
			return 1
			
		nPts = 50 if kwargs.get('nPoints') is None else kwargs.get('nPoints')
		pts = np.zeros((nPts, 2), float)
		pts[:, 0] = np.linspace(0, self.lCone, nPts, endpoint=True)
		pts[:, 1] = (0.5*self.dBase / (2 - k))*(2*pts[:, 0] / self.lCone - k*(pts[:, 0] / self.lCone)**2)
		sketch.addGeometry(self.makeBSpline(pts), False)
		sketch.addGeometry(self.plotInnerCurve(), False)
		
		return 0
		
		
				
	def makeBSpline(self, pts:np.ndarray) -> Part.BSplineCurve:
		"""Make a Part BSplineCurve for the array of 2D points input."""
		
		toInterp = [App.Vector(pts[i, 0], pts[i, 1]) for i in range(np.shape(pts)[0])]
		
		_finalbsp_poles = []
		_finalbsp_knots = []
		_finalbsp_mults = []
		_bsps = []
		
		_bsps.append(Part.BSplineCurve())
		_bsps[-1].interpolate(toInterp, PeriodicFlag=False)
		_bsps[-1].increaseDegree(3)
		_finalbsp_poles.extend(_bsps[-1].getPoles())
		_finalbsp_knots.extend(_bsps[-1].getKnots())
		_finalbsp_mults.extend(_bsps[-1].getMultiplicities())
		
		spline = Part.BSplineCurve(_finalbsp_poles, _finalbsp_mults, _finalbsp_knots, False, 3, None, False)
		
		del(_bsps)
		del(_finalbsp_poles)
		del(_finalbsp_knots)
		del(_finalbsp_mults)
		
		return spline
		
		
	def plotInnerCurve(self, xTip:float=0.0) -> list[Part.LineSegment]:
		"""Returns the line segments for the inside of the nosecone and shoulder"""
		
		pCentreFront = App.Vector(xTip, 0.0)
		pCentreRear = App.Vector(self.lCone + self.lShoulder, 0.0)
		pShoulderRear = App.Vector(self.lCone + self.lShoulder, 0.5*self.dShoulder)
		pShoulderFront = App.Vector(self.lCone, 0.5*self.dShoulder)
		pProfileRear = App.Vector(self.lCone, 0.5*self.dBase)
		
		segments = []
		segments.append(Part.LineSegment(pProfileRear, pShoulderFront))
		segments.append(Part.LineSegment(pShoulderFront, pShoulderRear))
		segments.append(Part.LineSegment(pShoulderRear, pCentreRear))
		segments.append(Part.LineSegment(pCentreRear, pCentreFront))
		
		return segments
		
		
		
myWin = InputWindow()
